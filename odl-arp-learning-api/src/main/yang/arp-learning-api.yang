module odl-calculator-api {
    yang-version 1;
    namespace "urn:opendaylight:params:xml:ns:yang:odl-calculator-api:api";
    prefix "odl-calculator-api";

    revision "2017-05-07" {
        description
            "Initial revision for Odl Test Api";
    }


    container odl-arp-api {
        config true;
        description "contains mapping of ip address to mac";
        list ip_to_mac {
            key "ip_address";
            leaf mac {
                description "ip address to mac address";
                type string; 
            }
            leaf ip_address{
                description "ip address to mac address";
                type string; 
            }
        }
    }
}
